module ntp {

  yang-version "1.1";

  namespace "http://pnc.xyz/yang/ntp";

  prefix "ntp";

  organization "The PNC Project";
  contact "a.matheus26@hotmail.com";
  description "NTP Server Config Model";

  revision "2021-02-25" {
    description
      "Initial setup";
    reference "1.1.0";
  }

  container ntp {
    leaf-list ntp-server {
      type string;
      description "NTP Server Configured";
    }
    description "NTP configurations";
  }
}
